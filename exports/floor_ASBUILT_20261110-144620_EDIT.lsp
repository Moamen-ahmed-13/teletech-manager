(vl-load-com)
(setq *tt-old-cmdecho* (getvar "CMDECHO"))
(setq *tt-old-filedia* (getvar "FILEDIA"))
(setq *tt-old-cmddia* (getvar "CMDDIA"))
(setq *tt-old-clayer* (getvar "CLAYER"))
(setvar "CMDECHO" 0)
(setvar "FILEDIA" 0)
(setvar "CMDDIA" 0)
(if (not (tblsearch "LAYER" "TELETECH-ASBUILT")) (command "_.-LAYER" "_M" "TELETECH-ASBUILT" ""))
(setq *tt-doc* (vla-get-ActiveDocument (vlax-get-acad-object)))
(setq *tt-ms* (vla-get-ModelSpace *tt-doc*))
(defun tt:clean-ent (d) (vl-remove-if (function (lambda (x) (member (car x) (quote (5 102 330 360))))) d))
(defun tt:clone-block (src new removeh childh childname watchh / btr bd e ed typ h ok skip targetnew)
  (setq btr (tblobjname "BLOCK" src))
  (if (or (null btr) (tblsearch "BLOCK" new)) nil
    (progn
      (setq bd (tt:clean-ent (entget btr)))
      (if (assoc 2 bd) (setq bd (subst (cons 2 new) (assoc 2 bd) bd)))
      (if (assoc 3 bd) (setq bd (subst (cons 3 new) (assoc 3 bd) bd)))
      (if (not (entmake bd)) nil
        (progn
          (setq e (entnext btr) ok T skip nil targetnew nil)
          (while (and e ok (/= "ENDBLK" (cdr (assoc 0 (entget e)))))
            (setq ed (entget e) typ (cdr (assoc 0 ed)) h (cdr (assoc 5 ed)))
            (cond
              ((and removeh h (= (strcase h) (strcase removeh))) (setq skip (= typ "INSERT")))
              ((and skip (member typ (quote ("ATTRIB" "SEQEND")))) (if (= typ "SEQEND") (setq skip nil)))
              (T
                (setq skip nil ed (tt:clean-ent ed))
                (if (and childh h (= (strcase h) (strcase childh)) (= typ "INSERT") childname (assoc 2 ed))
                  (setq ed (subst (cons 2 childname) (assoc 2 ed) ed)))
                (if (not (entmake ed)) (setq ok nil)
                  (if (and watchh h (= (strcase h) (strcase watchh))) (setq targetnew (cdr (assoc 5 (entget (entlast)))))))
              )
            )
            (setq e (entnext e))
          )
          (if (and ok e (= "ENDBLK" (cdr (assoc 0 (entget e)))))
            (if (entmake (tt:clean-ent (entget e))) (list new targetnew) nil)
            nil)
        )
      )
    )
  )
)
(defun tt:clone-path (blocks handles targeth removeit / i n src new childh childname result root ed btr flags target targetnew j ent parentbtr valid)
  (setq n (length blocks) i (1- (length blocks)) childname nil targetnew nil valid T j 0)
  (if (or (= n 0) (/= n (length handles))) nil
    (progn
      (setq target (handent targeth))
      (if (or (null target) (/= "INSERT" (cdr (assoc 0 (entget target)))) (equal 1 (cdr (assoc 66 (entget target))))) (setq valid nil))
      (while (and valid (< j n))
        (setq ent (handent (nth j handles)))
        (if (or (null ent) (/= "INSERT" (cdr (assoc 0 (entget ent)))) (equal 1 (cdr (assoc 66 (entget ent)))) (/= (strcase (nth j blocks)) (strcase (cdr (assoc 2 (entget ent))))))
          (setq valid nil)
          (if (> j 0)
            (progn
              (setq parentbtr (tblobjname "BLOCK" (nth (1- j) blocks)))
              (if (or (null parentbtr) (/= (cdr (assoc 330 (entget ent))) (cdr (assoc 5 (entget parentbtr))))) (setq valid nil))
            )
            (if (and (assoc 67 (entget ent)) (/= 0 (cdr (assoc 67 (entget ent))))) (setq valid nil))
          )
        )
        (setq j (1+ j))
      )
      (setq btr (tblobjname "BLOCK" (car (last blocks))))
      (if (or (not valid) (null btr) (/= (cdr (assoc 330 (entget target))) (cdr (assoc 5 (entget btr))))) (setq i -1))
      (while (>= i 0)
        (setq src (nth i blocks) btr (tblsearch "BLOCK" src) flags (if btr (cdr (assoc 70 btr)) 0))
        (if (or (null btr) (/= 0 (logand flags 29)) (= (substr src 1 1) "*"))
          (setq result nil valid nil i -1)
          (progn
            (setq new (strcat "TTAB_" (itoa (getvar "MILLISECS")) "_" (itoa i) "_" (itoa (setq *tt-clone-seq* (1+ *tt-clone-seq*)))))
            (setq childh (if (< i (1- n)) (nth (1+ i) handles) nil))
            (setq result (tt:clone-block src new (if (and removeit (= i (1- n))) targeth nil) childh childname (if (and (not removeit) (= i (1- n))) targeth nil)))
            (if result (progn (setq childname (car result)) (if (= i (1- n)) (setq targetnew (cadr result))) (setq i (1- i))) (setq valid nil i -1))
          )
        )
      )
      (if (and valid (> n 0) childname)
        (progn
          (setq root (handent (car handles)))
          (if (and root (= "INSERT" (cdr (assoc 0 (entget root)))) (or (null (assoc 67 (entget root))) (= 0 (cdr (assoc 67 (entget root))))))
            (progn
              (setq ed (entget root))
              (if (entmod (subst (cons 2 childname) (assoc 2 ed) ed)) (progn (entupd root) (list childname targetnew)) nil)
            )
            nil)
        )
        nil)
    )
  )
)
(setq *tt-clone-seq* 0)
(princ "\nTELETECH As-Built change 1: MOVE_ENDPOINT\n")
(setq *tt-e* (handent "7249F"))
(if *tt-e* (vla-Move (vlax-ename->vla-object *tt-e*) (vlax-3d-point (list 32208 -41698.0797803 0.0)) (vlax-3d-point (list 33208 -41069.8275605 0.0))) (princ "\nWARNING: target handle not found.\n"))
(princ "\nTELETECH As-Built change 2: DELETE_ENDPOINT\n")
(setq *tt-cloned* (tt:clone-path (quote ("access point wifi weather proof")) (quote ("721BB")) "8081F37" T))
(if *tt-cloned* (princ "\nNested endpoint removed from a private block-instance clone.\n") (princ "\nWARNING: nested clone/delete unsupported for this block; original instance left unchanged.\n"))
(princ "\nTELETECH As-Built change 3: DELETE_ENDPOINT\n")
(setq *tt-cloned* (tt:clone-path (quote ("access point wifi weather proof")) (quote ("721B6")) "8081F37" T))
(if *tt-cloned* (princ "\nNested endpoint removed from a private block-instance clone.\n") (princ "\nWARNING: nested clone/delete unsupported for this block; original instance left unchanged.\n"))
(command "_.REGEN")
(if *tt-old-clayer* (setvar "CLAYER" *tt-old-clayer*))
(if *tt-old-filedia* (setvar "FILEDIA" *tt-old-filedia*))
(if *tt-old-cmddia* (setvar "CMDDIA" *tt-old-cmddia*))
(if *tt-old-cmdecho* (setvar "CMDECHO" *tt-old-cmdecho*))
(princ "\nTELETECH As-Built changes applied. Use SAVEAS to create a NEW As-Built drawing.\n")
(princ)
